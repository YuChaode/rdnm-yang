module ietf-te-topology-fgnm-ext {
  yang-version 1.1;
  namespace "urn:ietf:params:xml:ns:yang:ietf-te-topology-fgnm-ext";
  prefix tet-fgnm-ext;

  import ietf-network {
    prefix "nw";
  }

  import ietf-network-topology {
    prefix "nt";
  }

  import ietf-te-topology {
    prefix "tet";
  }
  
  organization
    "IETF CCAMP Working Group";
  contact
    "WG Web: <http://tools.ietf.org/wg/ccamp/>
     WG List: <mailto:ccamp@ietf.org>

     Editor: Chaode Yu
             <mailto:yuchaode@huawei.com>
             Xing Zhao 
             <mailto:zhaoxing@caict.ac.cn>
             Yanxia Tan
             <mailto:tanyx11@chinaunicom.cn>
             Nigel Davis
             <mailto:ndavis@ciena.com>
             Daniel King
             <mailto:daniel@olddog.co.uk>";

  description
    "This module provide some extensions to TE topology model, based
    on transport fine-grain network management requirement";

  revision 2024-07-08 {
    description
      "Revision 1.0";
    reference
      "draft-yu-ccamp-te-fgnm-yang-01";
  }
  
  augment "/nw:networks/nw:network/nw:node/tet:te" {
    description 
      "Generic fine-grain network management extensions for 
      te node";
    
    uses node-fgnm-ext-grouping;
  }
  
  augment "/nw:networks/nw:network/nw:node/nt:termination-point/"
        + "tet:te" {
    description 
      "Generic fine-grain network management extensions for 
      termination point";
    
    uses tp-fgnm-ext-grouping;
  }
  
  augment "/nw:networks/nw:network/nw:node/tet:te" +
          "/tet:tunnel-termination-point" {
    description 
      "Generic fine-grain network management extensions for 
      te node";
    
    uses ttp-fgnm-ext-grouping;
  }  
  
  augment "/nw:networks/nw:network/nt:link/tet:te" {
    description 
      "Generic fine-grain network management extensions for link";
    
    uses link-fgnm-ext-grouping;
  }
  
  grouping node-fgnm-ext-grouping {
    choice layer-specific-extension {
      case generic {
      
      }
    }
  }
  
  grouping tp-fgnm-ext-grouping {
    choice layer-specific-extension {
      case generic {
      
      }
    }
  }
  
  grouping ttp-fgnm-ext-grouping {
    choice layer-specific-extension {
      case generic {
      
      }
    }
  }
  
  grouping link-fgnm-ext-grouping {
    choice layer-specific-extension {
      case generic {
      }
    }
  }
  
  rpc query-ttp-by-tps {
    input {
      list tp-list {
        key tp-id;
        leaf tp-id {
          type leafref {
            path "/nw:networks/nw:network/nw:node" + 
                 "/nt:termination-point/nt:tp-id";
          }
          
          description "the identifier of TP to querey";
        }
      }
    }
    
    output {
      leaf result {
        type enumeration {
          enum failed;
          enum partially-successful;
          enum successful;
        }
        
        description "the result of retrieval";
      }
      
      list result-list {
        key tp-id;
        
        leaf tp-id {
          type leafref {
            path "/nw:networks/nw:network/nw:node" + 
                 "/nt:termination-point/nt:tp-id";
          }
          
          description "the identifier of TP queried and returns TTPs";
        }
        
        list ttp-list {
          leaf tunnel-tp-id {
            type leafref {
              path "/nw:networks/nw:network/nw:node/tet:te" + 
                   "/tet:tunnel-termination-point/tet:tunnel-tp-id";
            }
            
            description "Identifier of TTP which is existing in the 
            topology. It is not required to return if it is not 
            existing in the topology.";
          }
          
          leaf ttp-name {
            type string;
            description "Name of TTP. If the ttp is idle, the default 
            name should be provided by the server and follow the 
            naming pattern of TMF814.";
          }
          leaf using-status {
            type enumeration {
              enum idle;
              enum bidirectional-used;
            }
          }
        }
      }
    }
  
  }
  
}
