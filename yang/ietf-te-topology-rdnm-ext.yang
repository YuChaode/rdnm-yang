module ietf-te-topology-rdnm-ext {
  yang-version 1.1;
  namespace "urn:ietf:params:xml:ns:yang:ietf-te-topology-rdnm-ext";
  prefix tet-rdnm-ext;

  import ietf-network {
    prefix "nw";
  }

  import ietf-network-topology {
    prefix "nt";
  }

  import ietf-te-topology {
    prefix "tet";
  }
  
  organization
    "IETF CCAMP Working Group";
  contact
    "WG Web: <http://tools.ietf.org/wg/ccamp/>
     WG List: <mailto:ccamp@ietf.org>

     Editor: Chaode Yu
             <mailto:yuchaode@huawei.com>
             Xing Zhao 
             <mailto:zhaoxing@caict.ac.cn>
             Yanxia Tan
             <mailto:tanyx11@chinaunicom.cn>
             Nigel Davis
             <mailto:ndavis@ciena.com>
             Daniel King
             <mailto:daniel@olddog.co.uk>";

  description
    "This module provide some extensions to TE topology model, based
    on transport Rich-Detail Network Management requirement";

  revision 2025-02-06 {
    description
      "Revision 1.0";
    reference
      "draft-yu-ccamp-te-rdnm-yang-00";
  }
  
  augment "/nw:networks/nw:network/nw:node/tet:te" {
    description 
      "Generic Rich-Detail Network Management extensions for 
      te node";
    
    uses node-rdnm-ext-grouping;
  }
  
  augment "/nw:networks/nw:network/nw:node/nt:termination-point/"
        + "tet:te" {
    description 
      "Generic Rich-Detail Network Management extensions for 
      termination point";
    
    uses tp-rdnm-ext-grouping;
  }
  
  augment "/nw:networks/nw:network/nw:node/tet:te" +
          "/tet:tunnel-termination-point" {
    description 
      "Generic Rich-Detail Network Management extensions for 
      te node";
    
    uses ttp-rdnm-ext-grouping;
  }  
  
  augment "/nw:networks/nw:network/nt:link/tet:te" {
    description 
      "Generic Rich-Detail Network Management extensions for link";
    
    uses link-rdnm-ext-grouping;
  }
  
  grouping node-rdnm-ext-grouping {
    description
	  "Generic extension of node.";
	  
    choice layer-specific-extension {
	  description
	    "The layer rate information.";
		
      case generic {
      
      }
    }
  }
  
  grouping tp-rdnm-ext-grouping {
    description
	  "Generic extension of TP.";
	  
    choice layer-specific-extension {
	  description
	    "The layer rate information.";
		
      case generic {
      
      }
    }
  }
  
  grouping ttp-rdnm-ext-grouping {
    description
	  "Generic extension of TTP.";
	  
    choice layer-specific-extension {
	  description
	    "The layer rate information.";
		
      case generic {
      
      }
    }
  }
  
  grouping link-rdnm-ext-grouping {
    description
	  "Generic extension of link.";
	  
    choice layer-specific-extension {
	  description
	    "The layer rate information.";
		
      case generic {
      }
    }
  }
  
  rpc query-ttp-by-tps {
    description
	  "Query all the TTPs on the LTPs";
	  
    input {
      list tp-list {
	    description
		  "the LTPs to retrieve.";
		  
        key tp-id;
        leaf tp-id {
          type leafref {
            path "/nw:networks/nw:network/nw:node" + 
                 "/nt:termination-point/nt:tp-id";
          }
          
          description "the identifier of TP to querey";
        }
      }
    }
    
    output {
      leaf result {
        type enumeration {
          enum failed;
          enum partially-successful;
          enum successful;
        }
        
        description "the result of retrieval";
      }
      
      list result-list {
	    description
		  "The result list.";
		  
        key tp-id;
        
        leaf tp-id {
          type leafref {
            path "/nw:networks/nw:network/nw:node" + 
                 "/nt:termination-point/nt:tp-id";
          }
          
          description "the identifier of TP queried and returns TTPs";
        }
        
        list ttp-list {
		  description
		    "the TTPs list for this LTP.";
			
          leaf tunnel-tp-id {
            type leafref {
              path "/nw:networks/nw:network/nw:node/tet:te" + 
                   "/tet:tunnel-termination-point/tet:tunnel-tp-id";
            }
            
            description "Identifier of TTP which is existing in the 
            topology. It is not required to return if it is not 
            existing in the topology.";
          }
          
          leaf ttp-name {
            type string;
            description "Name of TTP. If the ttp is idle, the default 
            name should be provided by the server and follow the 
            naming pattern of TMF814.";
          }
          leaf using-status {
            type enumeration {
              enum idle;
              enum bidirectional-used;
            }
          }
        }
      }
    }
  
  }
  
}
